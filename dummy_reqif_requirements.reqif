# Address Book Application

# Specification: Specification Document
- description: Address Book Application

## 1: Add a contact (Epic)
sample description

### 1 (UserStory)
As a user, I want to add a new contact to an address book
- status: not-started
- points: 10

### 2 (UserStory)
As a user, I want to add a new phone number to a contact
- status: not-started
- points: 20

## 2: Edit a contact (Epic)
sample description

### 3 (UserStory)
As a user, I want to edit the first name of a specific contact
- status: not-started
- points: 10

### 4 (UserStory)
As a user, I want to edit the last name of a specific contact
- status: not-started
- points: 20

### 5 (UserStory)
As a user, I want to edit a specific phone number of a specific contact
- points: 10
- status: not-started

## 3: Remove a contact (Epic)
sample description

### 6 (UserStory)
As a user, I want to remove an entire contact
- status: not-started
- points: 10

### 7 (UserStory)
As a user, I want to remove a specific property, such as a specific phone number, of a specific contact
- status: not-started
- points: 10
